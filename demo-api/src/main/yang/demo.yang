module demo {
    yang-version 1;
    namespace "urn:opendaylight:params:xml:ns:yang:demo";
    prefix "demo";

    revision "2018-11-07" {
        description "Initial revision of demo model";
    }
    
    container data-model {
    	
    	leaf attribute1 {
    		type string;
    	}
    	
    }
    
    rpc greet {
    	input {
    		leaf inputdata {
    			type string;
    		}
    	}
    	
    	output {
    		leaf outputdata {
    			type string;
    			}
    		}
    	}
    
    notification greet-message {
    	leaf message {
    	 	type string;
    	 }
    }
}
